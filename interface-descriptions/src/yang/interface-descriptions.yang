module interface-descriptions {

  namespace "http://example.com/interface-descriptions";
  prefix interface-descriptions;

  import ietf-inet-types {
    prefix inet;
  }
  import tailf-common {
    prefix tailf;
  }
  import tailf-ncs {
    prefix ncs;
  }

  description
    "Add description to an interface";

  revision 2016-01-01 {
    description
      "Initial revision.";
  }

  list interface-descriptions {
    description "This is an RFS skeleton service";

    key name;
    leaf name {
      tailf:info "Unique service id";
      tailf:cli-allow-range;
      type string;
    }

    uses ncs:service-data;
    ncs:servicepoint interface-descriptions-servicepoint;

    // may replace this with other ways of refering to the devices.

    leaf device {
      type leafref {
        path "/ncs:devices/ncs:device/ncs:name";
      }
    }
    leaf-list interface {
        type string;
    }
  }
}
